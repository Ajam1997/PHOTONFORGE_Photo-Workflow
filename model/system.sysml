// AUTO-GENERATED by scripts/export_sysml.py — DO NOT HAND-EDIT.
// Source of truth: requirements/requirement-map.yml
// Edit the YAML and re-run; this file regenerates from it.
// Mapping spec: dev-docs/architecture/sysml-export.md

package PHOTONFORGEPhotoWorkflow {

    // Bring SysMLv2 primitive scalar types (Real, String, Integer,
    // Boolean, etc.) into scope so attribute types resolve in Syson /
    // Cameo / any conformant parser.
    import ScalarValues::*;

    // ======= User Needs =======

    // -- User Need: UN-001 --
    requirement def UN_001 {
        doc /* pip install -e . exits 0. pytest --collect-only finds all test files.

**KPM:** NONE

**Stage:** 1

**Validated By:**
- (none yet) */
    }

    // -- User Need: UN-002 --
    requirement def UN_002 {
        doc /* claude agents lists @systems_lead, @software_lead, @software_lead, @verification, @validation. */
    }

    // -- User Need: UN-003 --
    requirement def UN_003 {
        doc /* Installation docs exist. A new user can stand up the pipeline on a fresh Yoga 910 by following the docs alone.

**KPM:** NONE

**Stage:** 1

**Validated By:**
- (none yet) */
    }

    // -- User Need: UN-010 --
    requirement def UN_010 {
        doc /* cluster_sessions() correctly groups fixture images by time and location.

**KPM:** KPM-1.10

**Stage:** 2

**Validated By:**
- e2e: Stage 2 milestone â€” UN-010 demonstrated end-to-end */
    }

    // -- User Need: UN-011 --
    requirement def UN_011 {
        doc /* deduplicate() archives images with dHash Hamming <= 2. No false positives.

**KPM:** KPM-1.6

**Stage:** 2

**Validated By:**
- e2e: Stage 2 milestone â€” UN-011 demonstrated end-to-end */
    }

    // -- User Need: UN-012 --
    requirement def UN_012 {
        doc /* score_sharpness() returns float in [0.0, 1.0] for all fixture images.

**KPM:** KPM-1.8

**Stage:** 2

**Validated By:**
- E2E: Stage 2 milestone â€” every photo in library.db has a non-null sharpness score
- inspection: dev-docs/photonforge-architecture.md V&V matrix shows FR-1.4 fully verified */
    }

    // -- User Need: UN-013 --
    requirement def UN_013 {
        doc /* score_composition() returns float in [0.0, 1.0].

**KPM:** KPM-1.8

**Stage:** 2

**Validated By:**
- e2e: Stage 2 milestone â€” UN-013 demonstrated end-to-end */
    }

    // -- User Need: UN-014 --
    requirement def UN_014 {
        doc /* score_exposure() returns float in [0.0, 1.0]. 11-zone entropy applied.

**KPM:** KPM-1.8

**Stage:** 2

**Validated By:**
- e2e: Stage 2 milestone â€” UN-014 demonstrated end-to-end */
    }

    // -- User Need: UN-020 --
    requirement def UN_020 {
        doc /* generate_name() returns a non-empty string. No raw DSC names in output.

**KPM:** KPM-1.2

**Stage:** 3

**Validated By:**
- e2e: Stage 2 milestone â€” UN-020 demonstrated end-to-end */
    }

    // -- User Need: UN-021 --
    requirement def UN_021 {
        doc /* library.db contains a record per image. XMP sidecar written per image.

**KPM:** NONE

**Stage:** 3

**Validated By:**
- e2e: Stage 2 milestone â€” UN-021 demonstrated end-to-end */
    }

    // -- User Need: UN-022 --
    requirement def UN_022 {
        doc /* generate_name() uses genre tag and top score dimensions to produce filenames that reflect subject and quality, not just scene description.

**KPM:** KPM-1.2

**Stage:** 3

**Validated By:**
- (none yet) */
    }

    // -- User Need: UN-030 --
    requirement def UN_030 {
        doc /* SD insertion triggers rsync to SSD within 10 seconds.

**KPM:** KPM-1.1

**Stage:** 4

**Validated By:**
- (none yet) */
    }

    // -- User Need: UN-031 --
    requirement def UN_031 {
        doc /* SSD mounts at /mnt/photon_ssd/001. library.db resides at /mnt/photon_ssd/001/darktable/library.db on cartridge.

**KPM:** NONE

**Stage:** 4

**Validated By:**
- (none yet) */
    }

    // -- User Need: UN-032 --
    requirement def UN_032 {
        doc /* safe_eject.sh flushes SQLite WAL. Zero corruption over 50 eject cycles.

**KPM:** KPM-1.4

**Stage:** 4

**Validated By:**
- e2e: Stage 3 milestone â€” UN-032 demonstrated end-to-end */
    }

    // -- User Need: UN-040 --
    requirement def UN_040 {
        doc /* rsync 1000 images to SSD per 120 seconds.

**KPM:** KPM-1.1

**Stage:** 6

**Validated By:**
- e2e: Stage 3 milestone â€” UN-040 demonstrated end-to-end */
    }

    // -- User Need: UN-041 --
    requirement def UN_041 {
        doc /* SD card is ejected and the user is notified that the photos have been transfered to the SSD.

**KPM:** KPM-1.4/KPM-1.1

**Stage:** 7

**Validated By:**
- (none yet) */
    }

    // -- User Need: UN-050 --
    requirement def UN_050 {
        doc /* photo-workflow exposes subcommands scan, dedup, score, name, sync, status. Each subcommand runs independently and enforces prerequisite stages.

**KPM:** NONE

**Stage:** 5

**Validated By:**
- (none yet) */
    }

    // -- User Need: UN-051 --
    requirement def UN_051 {
        doc /* ingest creates a SQLite DB file. Each subsequent stage reads and updates it. DB records per-photo stages_completed, scores, semantic_name, and errors.

**KPM:** NONE

**Stage:** 5

**Validated By:**
- (none yet) */
    }

    // -- User Need: UN-052 --
    requirement def UN_052 {
        doc /* score and name stages with --resume skip photos already completed. Checkpoint flush every 50 photos via atomic file replace. On crash, at most 50 photos of progress lost.

**KPM:** NONE

**Stage:** 5

**Validated By:**
- (none yet) */
    }

    // -- User Need: UN-053 --
    requirement def UN_053 {
        doc /* score and name stages print in-place progress line showing count/total, percentage, images/sec, ETA, and RSS. --verbose and --quiet flags control detail level.

**KPM:** NONE

**Stage:** 5

**Validated By:**
- (none yet) */
    }

    // -- User Need: UN-054 --
    requirement def UN_054 {
        doc /* Corrupt files or inference failures log a warning, record error in manifest, and continue. Failed photos are retried on --resume. Final summary reports error count.

**KPM:** NONE

**Stage:** 5

**Validated By:**
- (none yet) */
    }

    // ======= Functional Requirements =======

    // -- Functional Requirement: FR-1.1 (derives from UN-030) --
    requirement def FR_1_1 :> UN_030 {
        doc /* Automated Media Ingest. Implementation: udev-triggered rsync from SD to SSD cartridge

**Parent UN:** UN-030

**Verified By:**
- pytest: tests/test_ingest.py

**Validated By:**
- e2e: Stage 3 milestone â€” UN-030 demonstrated end-to-end */
    }

    // -- Functional Requirement: FR-1.10 (derives from UN-032) --
    requirement def FR_1_10 :> UN_032 {
        doc /* Safe Ejection. Implementation: WAL flush, sync, unmount via safe_eject.sh

**Parent UN:** UN-032

**Verified By:**
- pytest: tests/test_cartridge.py

**Validated By:**
- e2e: Stage 3 milestone â€” UN-032 demonstrated end-to-end */
    }

    // -- Functional Requirement: FR-1.2 (derives from UN-010) --
    requirement def FR_1_2 :> UN_010 {
        doc /* Spatio-Temporal Grouping. Implementation: Cluster if temporal delta < 500ms AND Hamming distance near 0

**Parent UN:** UN-010

**Verified By:**
- pytest: tests/test_grouping.py

**Validated By:**
- e2e: Stage 2 milestone â€” UN-010 demonstrated end-to-end */
    }

    // -- Functional Requirement: FR-1.3 (derives from UN-011) --
    requirement def FR_1_3 :> UN_011 {
        doc /* Perceptual Deduplication. Implementation: dHash near-duplicate detection (Hamming distance <= 2)

**Parent UN:** UN-011

**Verified By:**
- pytest: tests/test_dedup.py

**Validated By:**
- e2e: Stage 2 milestone â€” UN-011 demonstrated end-to-end */
    }

    // -- Functional Requirement: FR-1.4 (derives from UN-012) --
    requirement def FR_1_4 :> UN_012 {
        doc /* Sharpness Scoring. Implementation: Normalized Laplacian Variance

**Parent UN:** UN-012

**Verified By:**
- pytest: tests/test_sharpness.py::test_sharp_image_scores_high
- pytest: tests/test_sharpness.py::test_blurry_image_scores_low
- pytest: tests/test_sharpness.py::test_score_is_normalized
- pytest: tests/test_sharpness.py::test_missing_image_returns_zero
- pytest: tests/test_sharpness.py::test_fixture_sharp_scores_high
- pytest: tests/test_sharpness.py::test_fixture_blurry_scores_low

**Validated By:**
- E2E: Stage 2 milestone â€” sharpness column populated for all fixture images */
    }

    // -- Functional Requirement: FR-1.5 (derives from UN-013) --
    requirement def FR_1_5 :> UN_013 {
        doc /* Compositional Evaluation. Implementation: Rule-of-Thirds centroid proximity via saliency maps

**Parent UN:** UN-013

**Verified By:**
- pytest: tests/test_composition.py

**Validated By:**
- e2e: Stage 2 milestone â€” UN-013 demonstrated end-to-end */
    }

    // -- Functional Requirement: FR-1.6 (derives from UN-014) --
    requirement def FR_1_6 :> UN_014 {
        doc /* Exposure Assessment. Implementation: 11-zone luminance segmentation; entropy vs. IEA40K threshold

**Parent UN:** UN-014

**Verified By:**
- pytest: tests/test_exposure.py

**Validated By:**
- e2e: Stage 2 milestone â€” UN-014 demonstrated end-to-end */
    }

    // -- Functional Requirement: FR-1.7 (derives from UN-020) --
    requirement def FR_1_7 :> UN_020 {
        doc /* Local Semantic Naming. Implementation: Florence-2-base-ft INT8 ONNX: 4-model pipeline (vision encoder, embed tokens, encoder, decoder merged). 5-word descriptive slugs.

**Parent UN:** UN-020

**Verified By:**
- pytest: tests/test_naming.py

**Validated By:**
- e2e: Stage 2 milestone â€” UN-020 demonstrated end-to-end */
    }

    // -- Functional Requirement: FR-1.7.1 (derives from UN-020, UN-022) --
    requirement def FR_1_7_1 :> UN_020, UN_022 {
        doc /* Genre Detection Calibration and Back-Training */
    }

    // -- Functional Requirement: FR-1.7.2 (derives from UN-020, UN-022) --
    requirement def FR_1_7_2 :> UN_020, UN_022 {
        doc /* Multi-Genre Tagging Support */
    }

    // -- Functional Requirement: FR-1.8 (derives from UN-021) --
    requirement def FR_1_8 :> UN_021 {
        doc /* Darktable Integration. Implementation: SQLite writes to library.db + .xmp sidecar generation

**Parent UN:** UN-021

**Verified By:**
- pytest: tests/test_darktable.py

**Validated By:**
- e2e: Stage 2 milestone â€” UN-021 demonstrated end-to-end */
    }

    // -- Functional Requirement: FR-1.9 (derives from UN-031) --
    requirement def FR_1_9 :> UN_031 {
        doc /* Library Cartridge Management. Implementation: Physical Independent Volumes. ext4 labeled PHOTON-XXX. Each carries own DB + config.

**Parent UN:** UN-031

**Verified By:**
- pytest: tests/test_cartridge_manager.py

**Validated By:**
- e2e: Stage 3 milestone â€” UN-031 demonstrated end-to-end */
    }

    // ======= Non-Functional Requirements =======

    // -- Non-Functional Requirement: NFR-2.1 --
    requirement def NFR_2_1 :> UN_030 {
        doc /* Internet Independence. Specification: 100% offline at runtime. Initial provisioning (OS, packages, models) may use internet. Cloud export (Phase 3) user-opt-in only.

**Parent UN:** UN-030

**Linked Budget:** NONE

**Verified By:**
- (none yet)

**Validated By:**
- (none yet) */
    }

    // -- Non-Functional Requirement: NFR-2.2 --
    requirement def NFR_2_2 :> UN_030 {
        doc /* Resource Budget. Specification: Resource budget for the full scoring pipeline on the i7-7500U target:
- Peak RSS <= 1.5 GB during the score stage (CLIP + YOLO + Florence-2 INT8 all resident)
- Peak CPU <= 80% of available logical cores (leave headroom for the Darktable UI)

**Linked Budget:** NONE (this NFR *is* the resource budget)

**Verified By:**
- (none yet)

**Validated By:**
- (none yet)

_Created in Phase 4 to parent KPM-1.3 (Peak RSS) and KPM-1.9 (CPU Cap), which previously cited a nonexistent NFR-2.2. Constraint defined in CLAUDE.md (NFR-2.2)._ */
    }

    // -- Non-Functional Requirement: NFR-2.3 --
    requirement def NFR_2_3 :> UN_031 {
        doc /* Database Portability. Specification: Darktable library.db + user config on external SSD, not host filesystem.

**Parent UN:** UN-031

**Linked Budget:** NONE

**Verified By:**
- (none yet)

**Validated By:**
- (none yet) */
    }

    // -- Non-Functional Requirement: NFR-2.4 --
    requirement def NFR_2_4 :> UN_030 {
        doc /* Interactive UI Prompts. Specification: zenity dialogs if SD inserted without SSD connected.

**Parent UN:** UN-030

**Linked Budget:** NONE

**Verified By:**
- (none yet)

**Validated By:**
- (none yet) */
    }

    // -- Non-Functional Requirement: NFR-2.5 --
    requirement def NFR_2_5 :> UN_041 {
        doc /* Eject Notification. Specification: User-visible notification (zenity/desktop) when the SD card is safe to remove after photos transfer to the SSD. Distinct from NFR-2.4 (SD-inserted-without-SSD dialog).

**Parent UN:** UN-041

**Linked Budget:** NONE

**Verified By:**
- (none yet)

**Validated By:**
- (none yet) */
    }

    // ======= Interface Requirements =======

    // -- Interface Requirement: IF-1.1 --
    interface def IF_1_1 {
        doc /* Darktable Lua Plugin â†” CLI Orchestrator. Side A: Darktable Lua Plugin. Side B: CLI Orchestrator. Crosses: subprocess invocation + JSON-progress schema + PID sentinel + result store. Contract: see `requirements/interfaces/IF-1.1.md` for the full ICD.. */
        end Darktable Lua Plugin;
        end CLI Orchestrator;
    }

    // -- Interface Requirement: IF-2.1 --
    interface def IF_2_1 {
        doc /* Scoring subsystem internal contracts. Side A: region_router â†’ sub_scores. Side B: technical_gate + aesthetic_weighter â†’ fusion. Crosses: RegionSpec / SubScoreBundle / TechnicalResult / AestheticResult / FusionResult. Contract: see `requirements/interfaces/IF-2.1.md` for the full ICD.. */
        end region_router â†’ sub_scores;
        end technical_gate + aesthetic_weighter â†’ fusion;
    }

    // -- Interface Requirement: IF-3.1 --
    interface def IF_3_1 {
        doc /* Genre/Subject Classifier â†’ Scoring + Naming. Side A: Genre/Subject Classifier. Side B: Scoring System + Semantic Naming. Crosses: GenreResult (two-axis subject/type + distributions). Contract: see `requirements/interfaces/IF-3.1.md` for the full ICD.. */
        end Genre/Subject Classifier;
        end Scoring System + Semantic Naming;
    }

    // -- Interface Requirement: IF-3.2 --
    interface def IF_3_2 {
        doc /* Scoring + Naming â†’ Darktable Bridge. Side A: Scoring + Naming. Side B: Darktable Bridge. Crosses: FusionResult flat fields + GenreResult tags + semantic filename. Contract: see `requirements/interfaces/IF-3.2.md` for the full ICD.. */
        end Scoring + Naming;
        end Darktable Bridge;
    }

    // -- Interface Requirement: IF-4.1 --
    interface def IF_4_1 {
        doc /* Ingest & Cartridge â†’ Analysis Pipeline. Side A: Ingest & Cartridge. Side B: Analysis Pipeline. Crosses: staged file set + ingest manifest + EXIF. Contract: see `requirements/interfaces/IF-4.1.md` for the full ICD.. */
        end Ingest & Cartridge;
        end Analysis Pipeline;
    }

    // ======= KPMs (constraint blocks) =======

    // -- KPM: KPM-1.1 (aggregation: independent) --
    constraint def KPM_1_1 {
        attribute aggregation : String = "independent";
    }

    // -- KPM: KPM-1.10 (aggregation: independent) --
    constraint def KPM_1_10 {
        attribute aggregation : String = "independent";
    }

    // -- KPM: KPM-1.2 (aggregation: independent) --
    constraint def KPM_1_2 {
        attribute aggregation : String = "independent";
    }

    // -- KPM: KPM-1.3 (aggregation: independent) --
    constraint def KPM_1_3 {
        attribute aggregation : String = "independent";
    }

    // -- KPM: KPM-1.4 (aggregation: independent) --
    constraint def KPM_1_4 {
        attribute aggregation : String = "independent";
    }

    // -- KPM: KPM-1.5 (aggregation: independent) --
    constraint def KPM_1_5 {
        attribute aggregation : String = "independent";
    }

    // -- KPM: KPM-1.6 (aggregation: independent) --
    constraint def KPM_1_6 {
        attribute aggregation : String = "independent";
    }

    // -- KPM: KPM-1.7 (aggregation: independent) --
    constraint def KPM_1_7 {
        attribute aggregation : String = "independent";
    }

    // -- KPM: KPM-1.8 (aggregation: independent) --
    constraint def KPM_1_8 {
        attribute aggregation : String = "independent";
    }

    // -- KPM: KPM-1.9 (aggregation: independent) --
    constraint def KPM_1_9 {
        attribute aggregation : String = "independent";
    }

    // ======= Verification Cases (Stages) =======

    // -- Verification Case: Stage 1 — Scaffold & Foundation --
    verification case def Stage_1___Scaffold___Foundation {
        doc /* Stage 1 — Scaffold & Foundation */
        // verifies: UN_001
        // verifies: UN_002
        // verifies: UN_003
    }

    // -- Verification Case: Stage 2 — Core Engine --
    verification case def Stage_2___Core_Engine {
        doc /* Stage 2 — Core Engine */
        // verifies: UN_010
        // verifies: UN_011
        // verifies: UN_012
        // verifies: UN_013
        // verifies: UN_014
        // verifies: UN_020
        // verifies: UN_021
        // verifies: UN_022
    }

    // -- Verification Case: Stage 3 — Integration --
    verification case def Stage_3___Integration {
        doc /* Stage 3 — Integration */
        // verifies: UN_030
        // verifies: UN_031
        // verifies: UN_032
        // verifies: UN_040
        // verifies: UN_041
    }

    // -- Verification Case: Stage 4 — V&V --
    verification case def Stage_4___V_V {
        doc /* Stage 4 — V&V */
        // verifies: UN_050
        // verifies: UN_051
        // verifies: UN_052
        // verifies: UN_053
        // verifies: UN_054
    }

    // -- Verification Case: Stage 5 — Release --
    verification case def Stage_5___Release {
        doc /* Stage 5 — Release */
    }
}
